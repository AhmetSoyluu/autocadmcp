(defun c:GENERATE_UNIVERSAL_DRAFT ()
(command "._-layer" "M" "A-WALL" "C" "9" "" "M" "A-AXIS" "C" "1" "L" "CENTER" "" "M" "S-COL" "C" "2" "" "M" "M-DUCT" "C" "4" "" "M" "M-PIPE" "C" "6" "" "M" "E-POWER" "C" "1" "" "M" "E-DATA" "C" "5" "" "M" "TXT-ANNO" "C" "7" "" "M" "E-ZA-YANGIN" "C" "2" "" "M" "E-ZA-CCTV" "C" "6" "" "M" "E-OG-TRAFO" "C" "1" "" "M" "E-AG-BUSBAR" "C" "4" "" "M" "E-KANAL" "C" "9" "" "")
(setvar "CLAYER" "A-WALL")
(command "._rectang" "0.0,0.0" "400.0,260.0")
(command "._offset" "20.0" (entlast) "20.0,20.0")
(command "._line" "180.0,0.0" "180.0,260.0" "")
(command "._offset" "5.0" (entlast) "185.0,20.0")
(command "._break" (entlast) "180.0,80.0" "180.0,120.0")
(command "._arc" "180.0,80.0" "220.0,100.0" "180.0,120.0")
(command "._break" (entlast) "240.0,260.0" "300.0,260.0")
(setvar "CLAYER" "A-AXIS")
(command "._line" "50.0,0.0" "50.0,320.0" "")
(command "._line" "200.0,0.0" "200.0,320.0" "")
(command "._line" "350.0,0.0" "350.0,320.0" "")
(command "._line" "0.0,60.0" "420.0,60.0" "")
(command "._line" "0.0,180.0" "420.0,180.0" "")
(setvar "CLAYER" "S-COL")
(command "._rectang" "38.0,48.0" "62.0,72.0")
(command "._rectang" "188.0,48.0" "212.0,72.0")
(command "._rectang" "338.0,168.0" "362.0,192.0")
(setvar "CLAYER" "M-DUCT")
(command "._polyline" "40.0,420.0" "220.0,420.0" "220.0,500.0" "")
(command "._offset" "12" (entlast) "50.0,430.0")
(setvar "CLAYER" "M-PIPE")
(command "._line" "260.0,430.0" "380.0,430.0" "")
(command "._circle" "400.0,430.0" "14")
(command "._text" "J" "MC" "400.0,452.0" "2.2" "0" "PUMP")
(setvar "CLAYER" "E-AG-BUSBAR")
(command "._line" "80.0,320.0" "200.0,320.0" "")
(command "._line" "80.0,312.0" "200.0,312.0" "")
(setvar "CLAYER" "E-OG-TRAFO")
(command "._rectang" "420.0,300.0" "500.0,350.0")
(command "._text" "J" "MC" "460.0,325.0" "3" "0" "TRAFO")
(setvar "CLAYER" "E-POWER")
(command "._polyline" "200.0,316.0" "320.0,316.0" "320.0,330.0" "420.0,330.0" "")
(setvar "CLAYER" "E-ZA-YANGIN")
(command "._circle" "120.0,180.0" "6")
(command "._text" "J" "MC" "120.0,170.0" "2" "0" "SD")
(setvar "CLAYER" "E-ZA-CCTV")
(command "._line" "260.0,210.0" "272.0,218.0" "")
(command "._circle" "274.0,220.0" "3")
(setvar "CLAYER" "E-DATA")
(command "._line" "80.0,200.0" "320.0,200.0" "")
(command "._line" "200.0,120.0" "200.0,280.0" "")
(command "._line" "192.0,200.0" "196.0,200.0" "")
(command "._arc" "196.0,200.0" "200.0,208.0" "204.0,200.0")
(command "._line" "204.0,200.0" "208.0,200.0" "")
(command "._polyline" "60.0,80.0" "70.0,80.0" "60.0,90.0" "C")
(command "._text" "J" "MC" "65.0,92.0" "2" "0" "DATA")
(command "._rectang" "891.0,0.0" "1151.0,90.0")
(command "._text" "J" "ML" "901.0,70.0" "3" "0" "UNIVERSAL DRAFT")
(command "._text" "J" "ML" "901.0,45.0" "2.2" "0" "PROJECT TITLE BLOCK")
(command "._text" "J" "ML" "901.0,20.0" "2.2" "0" "DRAWN BY AUTOCADMCP")
(command "._rectang" "5000.0,0.0" "5260.0,140.0")
(command "._text" "J" "ML" "5010.0,120.0" "3" "0" "SYMBOL LEGEND")
(command "._text" "J" "ML" "5010.0,95.0" "2.2" "0" "WALL = Architectural Wall")
(command "._text" "J" "ML" "5010.0,77.0" "2.2" "0" "AXIS = Structural Grid")
(command "._text" "J" "ML" "5010.0,59.0" "2.2" "0" "DUCT = Mechanical Duct")
(command "._text" "J" "ML" "5010.0,41.0" "2.2" "0" "TRAFO = Transformer")
(command "._text" "J" "ML" "5010.0,23.0" "2.2" "0" "DATA = Weak Current Outlet")
(princ)
)
(c:GENERATE_UNIVERSAL_DRAFT)
